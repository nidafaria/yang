module interface-config {
  yang-version 1.1;

  namespace "urn:example:interface-config";
  prefix ifc;

  description
    "YANG model for a small mock interface configuration project.";

  revision 2026-10-18 {
    description "Initial version.";
  }

  container interfaces {
    list interface {
      key "name";

      leaf name {
        type string {
          length "1..32";
        }
      }

      leaf enabled {
        type boolean;
        mandatory true;
      }

      leaf mtu {
        type uint16 {
          range "576..9000";
        }
        default 1500;
      }
    }
  }
}
